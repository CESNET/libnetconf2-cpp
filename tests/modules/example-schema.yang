module example-schema {
    yang-version 1.1;
    prefix aha;
    namespace "http://example.com";

    leaf myLeaf {
        type string;
    }

    rpc myRpc {
      output {
          leaf myOutput {
            type string;
          }
      }
    }
}
